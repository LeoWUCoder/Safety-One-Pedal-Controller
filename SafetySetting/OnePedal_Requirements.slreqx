# OnePedal_Requirements

## SG-OPC-001: 单踏板控制系统应防止由其控制功能引起的车辆非预期加速。 (Functional)
由HARA中H1及相关危险事件导出的车辆级安全目标。
- Rationale: 限制非预期正向扭矩造成的碰撞风险。
- Keywords: draft, sg, one-pedal

### FSR-OPC-001: 当有效制动状态为已踩下时，单踏板控制功能应取消驱动或再生扭矩请求并输出0 Nm。 (Functional)
覆盖正常模式和受限故障模式中的制动优先行为。
- Rationale: 驾驶员制动操作必须优先于单踏板扭矩请求。
- Keywords: draft, fsr, one-pedal

#### TSR-OPC-001: CAN输入处理应根据制动信号可用状态输出原始制动状态或安全替代状态。 (Functional)
制动信号可用时透传，不可用时采用已踩下作为安全替代。
- Rationale: 制动信号丢失时禁止驱动扭矩比假定未制动更安全。
- Keywords: draft, tsr, one-pedal

##### SSR-OPC-001: 当制动CAN可用标志为真时，软件应输出接收到的制动踏板状态。 (Functional)
由CAN Signal Checker中制动信号切换路径实现。
- Rationale: 在通信有效时保持驾驶员输入语义。
- Keywords: draft, ssr, one-pedal

##### SSR-OPC-002: 当制动CAN可用标志为假时，软件应输出制动已踩下，并将CAN故障码的权重1位置为故障。 (Functional)
安全替代值为logical(1)，制动信号故障权重为1。
- Rationale: 通信失效时强制触发制动优先并报告故障来源。
- Keywords: draft, ssr, one-pedal

#### TSR-OPC-002: 扭矩状态机应在制动状态有效时选择零扭矩子状态。 (Functional)
适用于正常Drive、Reverse、Brake以及LimpMode中的Drive和Reverse状态。
- Rationale: 确保制动优先在最终扭矩计算中生效。
- Keywords: draft, tsr, one-pedal

##### SSR-OPC-003: 当控制器处于Drive、Reverse或Brake相关状态且制动状态为真时，软件应输出0 Nm。 (Functional)
由driveStop、reverseStop和barkStop状态实现；LimpMode中同样使用driveStop和reverseStop。
- Rationale: 避免驾驶员制动时仍存在控制器扭矩请求。
- Keywords: draft, ssr, one-pedal

### FSR-OPC-003: 当实际挡位为Drive且输入未触发故障模式时，单踏板控制功能应根据可信踏板位置计算正向驱动扭矩。 (Functional)
正常Drive模式提供0至80 Nm的线性正向扭矩。
- Rationale: 使正常驱动请求保持在模型定义的正向扭矩范围内。
- Keywords: draft, fsr, one-pedal

#### TSR-OPC-005: 正常Drive扭矩计算应采用可信踏板位置与80 Nm满量程的线性映射。 (Functional)
该映射仅在normalDrive且制动未踩下时执行。
- Rationale: 定义可验证的正常前进扭矩关系。
- Keywords: draft, tsr, one-pedal

##### SSR-OPC-010: 当软件处于正常Drive且制动未踩下时，应输出80倍可信踏板位置的正向扭矩。 (Functional)
当前实现为TorqueRequest_Nm=single(ThrottlePedalPosition)*80。
- Rationale: 实现0至80 Nm的正常驱动扭矩映射。
- Keywords: draft, ssr, one-pedal

## SG-OPC-002: 单踏板控制系统应防止由其控制功能引起的车辆非预期减速。 (Functional)
由HARA中H2及相关危险事件导出的车辆级安全目标。
- Rationale: 限制非预期再生制动造成的追尾风险。
- Keywords: draft, sg, one-pedal

### FSR-OPC-004: 当实际挡位为Brake且输入未触发故障模式时，单踏板控制功能应以踏板位置1/3为中性点计算驱动或再生扭矩。 (Functional)
中性点以下为再生制动，中性点以上为驱动。
- Rationale: 以确定的分段线性关系限制正常B挡扭矩方向和幅值。
- Keywords: draft, fsr, one-pedal

#### TSR-OPC-006: Brake模式扭矩计算应实现中性点1/3两侧的分段线性映射，并在制动踏板踩下时输出0 Nm。 (Functional)
驱动区满踏板输出80 Nm，再生区完全松踏板输出-80 Nm。
- Rationale: 定义B挡驱动与再生制动的可测试边界。
- Keywords: draft, tsr, one-pedal

##### SSR-OPC-011: 当软件处于正常Brake、制动未踩下且可信踏板位置大于1/3时，应输出120倍踏板位置减1/3的正向扭矩。 (Functional)
当前实现为1.5*80*(ThrottlePedalPosition-1/3)。
- Rationale: 实现B挡加速区0至80 Nm映射。
- Keywords: draft, ssr, one-pedal

##### SSR-OPC-012: 当软件处于正常Brake、制动未踩下且可信踏板位置小于或等于1/3时，应输出负240倍1/3减踏板位置的再生扭矩。 (Functional)
当前实现为-3*80*(1/3-ThrottlePedalPosition)。
- Rationale: 实现B挡再生区-80至0 Nm映射。
- Keywords: draft, ssr, one-pedal

##### SSR-OPC-013: 当软件处于正常Brake且制动状态为真时，应输出0 Nm。 (Functional)
由barkStop状态实现。
- Rationale: 确保B挡同样执行制动优先。
- Keywords: draft, ssr, one-pedal

## SG-OPC-003: 单踏板控制系统应防止由其控制功能引起的车辆加速不足。 (Functional)
由HARA中H3及相关危险事件导出的车辆级安全目标。
- Rationale: 在合理加速需求下维持可用的驱动能力或明确进入降级状态。
- Keywords: draft, sg, one-pedal

### FSR-OPC-005: 单踏板控制功能应使用三路踏板信号进行表决，并在单通道故障时继续输出由其余两路计算的可信踏板位置。 (Functional)
包含正常平均、单通道隔离和失去可信度后的零输出。
- Rationale: 利用三路输入提高单一踏板通道故障下的可用性。
- Keywords: draft, fsr, one-pedal

#### TSR-OPC-007: 踏板表决器应按0至1范围和通道差值阈值0.001执行有序故障判定。 (Functional)
判定顺序为A、B、C；未触发故障条件时输出三路平均值。
- Rationale: 准确描述当前Stateflow表决算法的范围和一致性检查。
- Keywords: draft, tsr, one-pedal

##### SSR-OPC-014: 当三路踏板信号未触发任何故障判定时，软件应输出三路信号的算术平均值。 (Functional)
当前实现为(a+b+c)/3。
- Rationale: 在三路信号可信时降低单通道噪声影响。
- Keywords: draft, ssr, one-pedal

##### SSR-OPC-015: 当A通道超出0至1范围，或A与B及A与C的差值均大于0.001时，软件应输出B与C的平均值并将传感器故障模式设为1。 (Functional)
对应Normal状态中的A通道优先判定。
- Rationale: 隔离被判定为故障的A通道。
- Keywords: draft, ssr, one-pedal

##### SSR-OPC-016: 在未判定A故障且B通道超出0至1范围或A与B的差值大于0.001时，软件应输出A与C的平均值并将传感器故障模式设为2。 (Functional)
对应Normal状态中的B通道有序判定。
- Rationale: 隔离被判定为故障的B通道。
- Keywords: draft, ssr, one-pedal

##### SSR-OPC-017: 在未判定A或B故障且C通道超出0至1范围或A与C的差值大于0.001时，软件应输出A与B的平均值并将传感器故障模式设为3。 (Functional)
对应Normal状态中的C通道有序判定。
- Rationale: 隔离被判定为故障的C通道。
- Keywords: draft, ssr, one-pedal

#### TSR-OPC-008: 踏板表决器应在已隔离一个通道后持续监控其余两路；若其余两路不再可信，应输出零并进入无可信输入状态。 (Functional)
单通道故障状态和NO_Trust状态不自动返回Normal。
- Rationale: 防止在剩余踏板信息不足时继续产生驱动请求。
- Keywords: draft, tsr, one-pedal

##### SSR-OPC-018: 当已隔离一个踏板通道且剩余两路的差值大于0.001，或任一剩余通道超出0至1范围时，软件应将传感器故障模式设为4并输出0。 (Functional)
A_Failure、B_Failure和C_Failure状态分别检查对应的剩余通道对。
- Rationale: 在无法形成可信双通道结果时提供零踏板安全替代值。
- Keywords: draft, ssr, one-pedal

##### SSR-OPC-019: 踏板表决器进入A、B、C单通道故障状态后不应自动返回Normal；进入NO_Trust后应保持NO_Trust并持续输出0。 (Functional)
当前Stateflow图不存在返回Normal的转换，NO_Trust使用自循环。
- Rationale: 保持已检测故障，避免瞬时恢复造成模式抖动。
- Keywords: draft, ssr, one-pedal

## SG-OPC-004: 单踏板控制系统应防止由其控制功能引起的车辆减速不足。 (Functional)
由HARA中H4及相关危险事件导出的车辆级安全目标。
- Rationale: 在B挡单踏板制动区提供与踏板请求一致的再生制动能力。
- Keywords: draft, sg, one-pedal

### FSR-OPC-006: 当Brake模式的再生制动使车速接近零时，单踏板控制功能应切换到以0 km/h为目标的低速控制。 (Functional)
低速控制由比例积分形式的状态逻辑实现。
- Rationale: 降低车辆穿越零速并向相反方向运动的风险。
- Keywords: draft, fsr, one-pedal

#### TSR-OPC-009: Brake模式低速控制应在再生子状态且车速小于或等于0.2 km/h时启用，并在踏板返回加速区时退出。 (Functional)
采用车速误差、累积误差以及退出复位。
- Rationale: 定义现有零速控制的进入、计算和退出条件。
- Keywords: draft, tsr, one-pedal

##### SSR-OPC-020: 当软件处于Brake再生子状态且车速小于或等于0.2 km/h时，应进入零速控制状态。 (Functional)
由barkDecele到brak0Velocity的转换实现。
- Rationale: 在接近静止时切换到专用低速控制。
- Keywords: draft, ssr, one-pedal

##### SSR-OPC-021: 在零速控制状态中，软件应令误差等于负车速、每周期累加误差，并按30倍误差加2倍累积误差计算扭矩请求。 (Functional)
当前实现为error=-VehicleSpeed_km_h；sumError=sumError+error；TorqueRequest_Nm=30*error+2*sumError。
- Rationale: 以现有PI形式将速度调节到0 km/h。
- Keywords: draft, ssr, one-pedal

##### SSR-OPC-022: 当软件处于零速控制且可信踏板位置大于1/3时，应退出零速控制、返回加速子状态并将累积误差复位为0。 (Functional)
由brak0Velocity退出转换和exit动作实现。
- Rationale: 避免零速积分量影响后续加速请求。
- Keywords: draft, ssr, one-pedal

## SG-OPC-005: 单踏板控制系统应防止车辆因其控制功能而向错误方向运动。 (Functional)
由HARA中H5及相关危险事件导出的车辆级安全目标。
- Rationale: 通过挡位互锁、方向相关扭矩控制和零速控制降低错误方向运动风险。
- Keywords: draft, sg, one-pedal

### FSR-OPC-007: 单踏板控制功能应依据制动状态、请求挡位和有符号车速管理P、R、N、D及Brake实际挡位。 (Functional)
挡位转换条件按现有Stateflow状态机定义。
- Rationale: 阻止在不满足制动或速度条件时直接产生相反方向扭矩。
- Keywords: draft, fsr, one-pedal

#### TSR-OPC-010: 正常模式挡位状态机应以Park初始化，并按请求挡位、制动状态、车速和踏板位置执行状态转换。 (Functional)
记录现有P、R、N、D和Brake状态转换条件。
- Rationale: 建立可验证的挡位互锁行为。
- Keywords: draft, tsr, one-pedal

##### SSR-OPC-023: 正常模式初始化时，软件应进入Park、输出实际挡位Park并输出0 Nm。 (Functional)
NoFailureDetected默认进入Park，Park状态持续输出0 Nm。
- Rationale: 为启动提供无驱动扭矩的确定状态。
- Keywords: draft, ssr, one-pedal

##### SSR-OPC-024: 当软件处于Park、制动已踩下且请求挡位不是Park时，应转入Neutral。 (Functional)
由Park到Neutral转换实现。
- Rationale: 通过Neutral中间状态执行离开驻车的挡位管理。
- Keywords: draft, ssr, one-pedal

##### SSR-OPC-025: 当软件处于Neutral、车速大于-5 km/h且小于5 km/h、制动已踩下且请求Park时，应转入Park。 (Functional)
速度条件采用VehicleSpeed_km_h<5且>-5。
- Rationale: 仅在接近静止且制动时接受驻车请求。
- Keywords: draft, ssr, one-pedal

##### SSR-OPC-026: 当软件处于Neutral、车速小于5 km/h、制动已踩下且请求Reverse时，应转入Reverse。 (Functional)
当前实现未设置反向车速下界，需求准确反映现有转换条件。
- Rationale: 记录并验证现有倒车挡互锁。
- Keywords: draft, ssr, one-pedal

##### SSR-OPC-027: 当软件处于Neutral、车速大于-5 km/h、制动已踩下且请求Drive或Brake时，应转入Drive。 (Functional)
Brake请求先进入Drive，随后由Drive到Brake条件决定是否进入Brake。
- Rationale: 记录并验证现有前进方向挡位互锁。
- Keywords: draft, ssr, one-pedal

##### SSR-OPC-028: 当软件处于Reverse且请求挡位不再为Reverse时，应转入Neutral。 (Functional)
由Reverse到Neutral转换实现。
- Rationale: 离开倒车挡时先进入零扭矩Neutral状态。
- Keywords: draft, ssr, one-pedal

##### SSR-OPC-029: 当软件处于Drive且请求Neutral时，应转入Neutral；当请求Brake且可信踏板位置大于1/3时，应转入Brake。 (Functional)
由Drive到Neutral和Drive到Brake转换实现。
- Rationale: 记录当前Drive状态的退出条件。
- Keywords: draft, ssr, one-pedal

##### SSR-OPC-030: 当软件处于Brake且请求挡位为Drive或Neutral时，应转入Drive。 (Functional)
当前实现将Drive或Neutral请求均转换到Drive。
- Rationale: 准确记录现有Brake退出行为，供测试和后续安全评审。
- Keywords: draft, ssr, one-pedal

### FSR-OPC-008: 当安全相关CAN输入不可用时，单踏板控制功能应使用现有安全替代值并输出可区分故障来源的故障码。 (Functional)
覆盖制动、挡位和车速三个可用性标志及其位权故障码。
- Rationale: 在输入不可用时保持确定的控制输入并触发LimpMode。
- Keywords: draft, fsr, one-pedal

#### TSR-OPC-011: CAN信号检查器应分别处理制动、挡位和车速可用标志，并以权重1、2和4组合CAN故障码。 (Functional)
当前实现仅处理外部提供的可用性标志，不实现内部超时、范围或新鲜度诊断。
- Rationale: 准确限定CAN检查器的实际诊断边界。
- Keywords: draft, tsr, one-pedal

##### SSR-OPC-031: 仅当挡位CAN和车速CAN可用标志均为真时，软件才应输出接收到的挡位请求；否则应输出Neutral作为替代挡位。 (Functional)
挡位切换控制输入为AT可用与车速可用的逻辑与。
- Rationale: 在挡位或车速信息不可用时避免使用未经确认的方向请求。
- Keywords: draft, ssr, one-pedal

##### SSR-OPC-032: 当车速CAN可用标志为真时，软件应输出接收到的车速；当该标志为假时，应输出0 km/h。 (Functional)
由车速信号Switch和常量0实现。
- Rationale: 为不可用车速提供确定的替代值并配合故障模式限制扭矩。
- Keywords: draft, ssr, one-pedal

##### SSR-OPC-033: 软件应将制动CAN不可用、挡位CAN不可用和车速CAN不可用分别编码为1、2和4，并将有效故障权重相加形成0至7的CAN故障码。 (Functional)
由三个NOT、权重常量和求和模块实现。
- Rationale: 使故障来源可以由CAN故障码按位区分。
- Keywords: draft, ssr, one-pedal

##### SSR-OPC-034: 软件应分别输出int8类型的传感器故障模式和CAN故障模式。 (Functional)
根级输出端口为Sensor Fail Mode和CAN BUS Fail Mode。
- Rationale: 向外部测试或上层诊断提供当前输入故障状态。
- Keywords: draft, ssr, one-pedal

## SG-OPC-006: 单踏板控制系统应在相关FTTI内检测安全相关输入故障并完成模型规定的故障反应。 (Functional)
由HARA中跨安全目标的检测与反应约束导出；本需求仅覆盖模型已实现的故障码、模式切换和受限扭矩反应。
- Rationale: 保证已实现的诊断结果能够在控制周期内触发确定的受限模式。
- Keywords: draft, sg, one-pedal

### FSR-OPC-002: 当踏板诊断或CAN可用性诊断报告故障时，单踏板控制功能应进入受限功率模式。 (Functional)
故障模式由踏板故障码和CAN故障码的逻辑或触发。
- Rationale: 通过降低故障情况下的驱动能力限制非预期加速风险。
- Keywords: draft, fsr, one-pedal

#### TSR-OPC-003: 故障模式管理应聚合踏板故障状态和CAN故障状态，并保存进入故障前的实际挡位。 (Functional)
任一非零故障状态触发LimpMode，同时记录AT_State。
- Rationale: 为受限模式选择与故障前运行方向一致的状态。
- Keywords: draft, tsr, one-pedal

##### SSR-OPC-004: 当踏板故障状态或CAN故障状态非零时，软件应保存当前实际挡位并从正常模式切换到LimpMode。 (Functional)
isFailMode由SensorFailMode和CAN_BUS_Fail_Mode逻辑或形成。
- Rationale: 确保任一已检测输入故障触发受限控制。
- Keywords: draft, ssr, one-pedal

##### SSR-OPC-005: 当软件处于LimpMode、复位输入为真且所有受监控故障均已清除时，软件应返回正常模式。 (Functional)
仅当ThrottlePedalSensorReset等于1，并且Sensor Fail Mode等于0且CAN BUS Fail Mode等于0（即isFailMode为假）时，软件才允许退出LimpMode；若任一故障状态仍为非零，软件应保持LimpMode。
- Rationale: 防止在故障仍然存在时因复位请求短暂退出LimpMode，并在下一控制周期再次进入LimpMode，从而避免模式抖动和非预期恢复正常控制。
- Keywords: draft, ssr, one-pedal

#### TSR-OPC-004: 受限功率模式应根据故障前挡位选择驻车、空挡、受限前进或受限倒车行为。 (Functional)
Brake和Drive映射到受限Drive，Reverse映射到受限Reverse，Neutral映射到Neutral，其余路径进入Park。
- Rationale: 在故障状态下保持可预测的方向和功率边界。
- Keywords: draft, tsr, one-pedal

##### SSR-OPC-006: 进入LimpMode时，若故障前挡位为Drive或Brake，软件应选择受限Drive；若为Reverse应选择受限Reverse；若为Neutral应选择Neutral；其他情况应选择Park。 (Functional)
由LimpMode初始连接点对lastTimeMode的分支实现。
- Rationale: 保持故障前运动方向并为未匹配状态提供驻车默认值。
- Keywords: draft, ssr, one-pedal

##### SSR-OPC-007: 当软件处于受限Drive、制动未踩下且车速小于20 km/h时，应输出8倍可信踏板位置的正扭矩；车速大于或等于20 km/h时应输出0 Nm。 (Functional)
当前实现为TorqueRequest_Nm=ThrottlePedalPosition*80/10。
- Rationale: 限制故障模式下的正向扭矩和最高受驱动车速。
- Keywords: draft, ssr, one-pedal

##### SSR-OPC-008: 当软件处于受限Reverse且制动未踩下时，应输出负4倍可信踏板位置的反向扭矩。 (Functional)
当前实现为-8*ThrottlePedalPosition*60/12/10，即-4*ThrottlePedalPosition Nm。
- Rationale: 限制故障模式下的反向扭矩。
- Keywords: draft, ssr, one-pedal

##### SSR-OPC-009: 当软件处于LimpMode的Park或Neutral状态，或者受限Drive或Reverse状态下制动已踩下时，应输出0 Nm。 (Functional)
由LimpMode的Park、Neutral、driveStop和reverseStop状态实现。
- Rationale: 在非驱动状态或制动请求下禁止扭矩。
- Keywords: draft, ssr, one-pedal
